/**
 * TestCases — verification case definitions for core CSCI tests.
 *
 * LEAF FILE. Globally unique name "TestCases".
 * Assembled into Verification::TestCases by the namespace hub.
 *
 * NOTE: In SysIDE 0.8.x, `verification def` does not produce a Classifier,
 * so typing a verification usage by one triggers a usage-feature-typing
 * warning. Verification usages in Traceability.sysml are left untyped.
 * Revisit when SysIDE exposes VerificationCaseDefinition as a first-class type.
 *
 * These defs serve as named anchors for test planning documentation.
 */
package TestCases {
    verification def ProcessingCapabilityTest_Def;
    verification def IntegrationCapabilityTest_Def;
    verification def ExternalDataInterfaceTest_Def;
    verification def SystemAvailabilityAnalysis_Def;
    verification def ProgrammingLanguageInspection_Def;
}
