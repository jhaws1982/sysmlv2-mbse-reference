// Target spec: SysML v2 2025-07 (SysIDE 0.8.x compatible)
/**
 * ProgramB_StakeholderDefs — Program B specific stakeholder roles.
 */
package ProgramB_StakeholderDefs {

    part def ProgramB_Integrator {
        doc /* External integrator responsible for Program B interface contracts. */
    }

    part def ProgramB_SafetyOfficer {
        doc /* Safety officer responsible for Program B safety case. */
    }
}
